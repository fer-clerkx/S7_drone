# stakeholderRequirements

## STAKEHOLDER_08: Flight maneuver (Functional)
The drone shall be able to perform take off and landing vertically.

## STAKEHOLDER_09: Maneuverability (Functional)
The drone should be able to move freely in all 6 directions.

## STAKEHOLDER_10: Maneuverability (Functional)
The drone can freely rotate along the Z-axis whilst stationery.

## STAKEHOLDER_03: Control (Functional)
The drone can be controlled remotely.

## STAKEHOLDER_04: Control (Functional)
The drone can be controlled autonomously.

### STAKEHOLDER_05: Autonomy (Functional)
Whilst flying autonously, the drone can avoid obstacles.

### STAKEHOLDER_06: Landing accuracy (Functional)
The drone can land autonomously with an accuracy of 1 meter.

## STAKEHOLDER_13: Performance (Functional)
The drone can fly at a height of at least 2 meters.

## STAKEHOLDER_14: Performance (Functional)
The drone shall have a flight range of at least 10 meters.

## STAKEHOLDER_02: Communication (Functional)
The drone can remain in contact with the remote controller at an unobstructed distance of at least 10 meters.

## STAKEHOLDER_11: Package (Functional)
The drone can carry a package with a mass of at least 10 grams.

## STAKEHOLDER_12: Package (Functional)
The drone can attach and release a package without physical human intervention.

## STAKEHOLDER_15: Safety (Functional)
The drone can autonously shut down when dangerous conditions are sensed.

## STAKEHOLDER_07: Drone platform (Functional)
The For The Win Robotics Parrot Mambo drone has to be used.
