# systemRequirements

## SENS_01: Zone detection (Functional)
The camera sensor can detect a 10 cm wide green mark when within the cameras field of vision.

## CONTROL_04: Positioning (Functional)
The drone can be positioned whilst in the air within 1 meter horizontally of a green mark.

## GRABBER_01: Grabber manual control (Functional)
The grabber can be engaged and disengaged manually.

## GRABBER_02: Grabber autonomous control (Functional)
The grabber can be engaged autonomously before initial takeoff.

## GRABBER_03: Grabber autonomous control (Functional)
The grabber can be disengaged autonomously after landing at the drop off site.

## GRABBER_04: Grabber capacity (Functional)
The grabber can carry an object with a mass of 10 grams.

## CONTROL_01: Liftoff autonomous (Functional)
The drone can liftoff autonomously after engaging the grabber at the pickup point.

## CONTROL_02: Liftoff autonomous (Functional)
The drone can liftoff autonomously after disengaging the grabber at the dropoff point.

## CONTROL_03: Zone detection (Functional)
The drone will fly up vertically until the landing zone is detected or the flight ceiling is reached.

## CONTROL_06: Landing autonomous (Functional)
The drone can land autonomously after hovering over the landing zone and being clear of obstacles.

## CONTROL_07: Emergency Shutdown (Functional)
The drone will autonomously stop the motors after a collision.

## SENS_02: Obstacle detection (Functional)
Red obstacles directly underneath the drone are detected.

## CONTROL_05: Obstacle avoidance (Functional)
If an obstacle is detected underneath the drone in the landing zone, the drone will move in the direction of the marker until the obstacle is cleared.

## CONTROL_08: Nominal Shutdown (Functional)
The drone will shutdown after completing the delivery (landed back at the pickup point).
